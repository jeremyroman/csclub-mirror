CSC-MIB DEFINITIONS ::= BEGIN

IMPORTS
    MODULE-IDENTITY, OBJECT-TYPE, Counter32, Gauge32, Counter64,
    Integer32, TimeTicks, mib-2, enterprises,
    NOTIFICATION-TYPE                        FROM SNMPv2-SMI
    TEXTUAL-CONVENTION, DisplayString,
    PhysAddress, TruthValue, RowStatus,
    TimeStamp, AutonomousType, TestAndIncr   FROM SNMPv2-TC
    MODULE-COMPLIANCE, OBJECT-GROUP,
    NOTIFICATION-GROUP                       FROM SNMPv2-CONF
    snmpTraps                                FROM SNMPv2-MIB
    IANAifType                               FROM IANAifType-MIB;

csclub OBJECT IDENTIFIER ::= { enterprises 27934 }

cscMIB MODULE-IDENTITY
    LAST-UPDATED "200905080000Z"
    ORGANIZATION "University of Waterloo Computer Science Club"
    CONTACT-INFO "systems-committee@csclub.uwaterloo.ca"
    DESCRIPTION  "Computer Science Club Local MIBs"
    REVISION     "200905080000Z"
    DESCRIPTION  "Initial revision"
    ::= { csclub 2 }

netsched OBJECT IDENTIFIER ::= { cscMIB 2 }

classTable OBJECT-TYPE
    SYNTAX      SEQUENCE OF ClassEntry
    MAX-ACCESS  not-accessible
    ::= { netsched 1 }

classEntry OBJECT-TYPE
    SYNTAX      ClassEntry
    MAX-ACCESS  not-accessible
    INDEX       { ClassIndex }
    ::= { classTable 1 }

ClassEntry ::=
    SEQUENCE {
        classIndex              Integer32,
        classOutOctets          Counter64,
    }

classIndex OBJECT-TYPE
    SYNTAX      Integer32
    MAX-ACCESS  read-only
    STATUS      current
    ::= { classEntry 1 }

classOutOctets OBJECT-TYPE
    SYNTAX      Counter64
    MAX-ACCESS  read-only
    ::= { classEntry 2 }
